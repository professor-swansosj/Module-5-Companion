module cisco-catalyst-interface {
  yang-version 1.1;
  namespace "http://cisco.com/ns/yang/cisco-catalyst-interface";
  prefix cat-int;

  organization "Cisco Systems";
  contact "Cisco Support";
  
  description
    "Sample YANG model for Cisco Catalyst interface configuration.
     This is a simplified version for educational purposes.";

  revision 2025-01-01 {
    description "Initial version for educational use";
  }

  // Import standard modules
  import ietf-interfaces {
    prefix if;
  }

  import ietf-yang-types {
    prefix yang;
  }

  // Augment standard interface model
  augment "/if:interfaces/if:interface" {
    description "Cisco-specific interface configuration";

    container switchport {
      when "../if:type = 'ethernetCsmacd'";
      description "Layer 2 switchport configuration";

      leaf mode {
        type enumeration {
          enum access {
            description "Access port mode";
          }
          enum trunk {
            description "Trunk port mode";
          }
          enum dynamic-auto {
            description "Dynamic auto negotiation";
          }
        }
        default "access";
        description "Switchport mode";
      }

      leaf access-vlan {
        when "../mode = 'access'";
        type uint16 {
          range "1..4094";
        }
        default 1;
        description "Access VLAN ID";
      }

      leaf-list trunk-vlans {
        when "../mode = 'trunk'";
        type uint16 {
          range "1..4094";
        }
        description "List of allowed VLANs on trunk";
      }

      leaf native-vlan {
        when "../mode = 'trunk'";
        type uint16 {
          range "1..4094";
        }
        default 1;
        description "Native VLAN for trunk port";
      }
    }

    container ethernet {
      when "../if:type = 'ethernetCsmacd'";
      description "Ethernet-specific configuration";

      leaf duplex {
        type enumeration {
          enum auto {
            description "Auto-negotiate duplex";
          }
          enum full {
            description "Force full duplex";
          }
          enum half {
            description "Force half duplex";
          }
        }
        default "auto";
        description "Duplex mode";
      }

      leaf speed {
        type enumeration {
          enum auto {
            description "Auto-negotiate speed";
          }
          enum 10 {
            description "10 Mbps";
          }
          enum 100 {
            description "100 Mbps";
          }
          enum 1000 {
            description "1 Gbps";
          }
          enum 10000 {
            description "10 Gbps";
          }
        }
        default "auto";
        description "Interface speed";
      }
    }

    container power {
      description "Power over Ethernet configuration";

      leaf inline {
        type enumeration {
          enum auto {
            description "Auto power detection";
          }
          enum never {
            description "Never provide power";
          }
          enum static {
            description "Static power allocation";
          }
        }
        default "auto";
        description "PoE mode";
      }

      leaf max-watts {
        when "../inline != 'never'";
        type decimal64 {
          fraction-digits 1;
          range "0.0..90.0";
        }
        description "Maximum power in watts";
      }
    }
  }

  // Operational state data
  augment "/if:interfaces-state/if:interface" {
    description "Cisco-specific operational data";

    container switchport-state {
      description "Switchport operational state";

      leaf operational-mode {
        type enumeration {
          enum access;
          enum trunk;
          enum routed;
        }
        config false;
        description "Current operational mode";
      }

      leaf operational-vlan {
        type uint16;
        config false;
        description "Current operational VLAN";
      }
    }

    container power-state {
      description "Power over Ethernet state";

      leaf power-allocated {
        type decimal64 {
          fraction-digits 1;
        }
        units "watts";
        config false;
        description "Currently allocated power";
      }

      leaf power-used {
        type decimal64 {
          fraction-digits 1;
        }
        units "watts";
        config false;
        description "Actually consumed power";
      }

      leaf device-detected {
        type boolean;
        config false;
        description "Powered device detected";
      }
    }
  }
}
